module create-rpc {
    yang-version "1.1";
    namespace "https://github.com/johneandredejesus/Study/blob/main/yang/create-rpc.yang";
    prefix "c-rpc";

    contact
      "johneandredejesus@gmail.com";
    organization
      "JAJ";
    revision 2021-07-06 {
        description
          "First Creation.";
    }

    rpc get-status {
        input {
            leaf id {
                type int8;
            }
        }
        output {
            leaf is-on {
                type boolean;
            }
        }
    }
}
